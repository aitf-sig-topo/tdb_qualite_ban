FME workspace CreationReferentielCommunalAvecClassementDensite.fmw

Parameters:
- SourceDataset_OGCGEOPACKAGE = $(FME_MF_DIR)ADE-COG-CARTO-PE_4-0_GPKG_LAMB93_FXX-ED2025-01-01.gpkg   # GeoPackage File
- SourceDataset_XLSXR = $(FME_MF_DIR)fichier_diffusion_2025.xlsx   # Source Microsoft Excel File(s)
- DestDataset_GEOJSON = $(FME_MF_DIR)referentiel_communal.geojson   # Destination GeoJSON File
- SourceDataset_SHAPEFILE_9 = $(FME_MF_DIR)Martinique D972\COMMUNE.shp   # Source Esri Shapefile(s)
- SourceDataset_SHAPEFILE_7 = $(FME_MF_DIR)Mayotte D976\COMMUNE.shp   # Source Esri Shapefile(s)
- SourceDataset_SHAPEFILE_6 = $(FME_MF_DIR)La Reunion D974\COMMUNE.shp   # Source Esri Shapefile(s)
- SourceDataset_SHAPEFILE_8 = $(FME_MF_DIR)Guyane D973\COMMUNE.shp   # Source Esri Shapefile(s)
- SourceDataset_SHAPEFILE = $(FME_MF_DIR)Guadeloupe_D971\COMMUNE.shp   # Source Esri Shapefile(s)

Readers:
- OGCGEOPACKAGE_1: OGCGEOPACKAGE from $(SourceDataset_OGCGEOPACKAGE) in EPSG:2154
- XLSXR_1: XLSXR from $(SourceDataset_XLSXR)
- SHAPEFILE_1: SHAPEFILE from $(SourceDataset_SHAPEFILE)
- SHAPEFILE_2: SHAPEFILE from $(SourceDataset_SHAPEFILE_9)
- SHAPEFILE_3: SHAPEFILE from $(SourceDataset_SHAPEFILE_7)
- SHAPEFILE_4: SHAPEFILE from $(SourceDataset_SHAPEFILE_6)
- SHAPEFILE_5: SHAPEFILE from $(SourceDataset_SHAPEFILE_8)

Writers:
- GEOJSON_1: GEOJSON to $(DestDataset_GEOJSON) in EPSG:3857

Note: Fichier insee contenant le classement par densite de la commune / source : https://www.insee.fr/fr/information/8571524
Maille communale (reader XLSXR_1)
    attributes: CODGEO number(5,0), LIBGEO char(29), DENS number(1,0), LIBDENS char(21), PMUN22 number(5,0), P1 number(1,0), P2 number(19,15), P3 number(31,15), DENS_AAV number(1,0), LIBDENS_AAV char(21), DENS7 number(1,0), LIBDENS7 char(32)
    -> FeatureMerger [SUPPLIER]
Note: FRANCE METROPOLITAINE / BD ADMIN EXPRESS COG petite échelle de l'IGN / Source : https://geoservices.ign.fr/telechargement-api/ADMIN-EXPRESS-COG-CARTO-PE?zone=FXX&format=GPKG
commune (reader OGCGEOPACKAGE_1)
    attributes: cleabs text(24), nom_officiel text, nom_officiel_en_majuscules text, statut text, code_insee text, population mediumint, date_du_recensement date, organisme_recenseur text(16), code_insee_du_canton text, code_insee_de_l_arrondissement text(5), code_insee_du_departement text, code_insee_de_la_region text, codes_siren_des_epci text, code_postal text(5), superficie_cadastrale mediumint, fid int,PrimaryKey
    -> FeatureMerger [REQUESTOR]
Note: Jointure entre les deux sources de données par le code insee de la commune
FeatureMerger
    ATTR_ACCUM_MODE = Merge Supplier
    ATTR_CONFLICT_RES_LOOKUP = REQUESTOR_IF_CONFLICT
    IGNORE_NULLS = No
    JOIN_KEYS = @Value(code_insee) @Value(CODGEO) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> BulkAttributeRenamer
Note: passe attributs en minuscules
BulkAttributeRenamer
    ATTRCHOICE_ACTION = NONPROTECTEDFME
    CASE_CHANGE_TYPE = lower
    MODE_CHOICE = RENAME
    PATTERN_ACTION_DISP = CASECHANGE
    ATTRCHOICE = All Attributes
    -> AttributeKeeper
Note: Ne conserve que les attributs utiles
AttributeKeeper
    CREATE_BULK_MODE_FEATURES = NO
    KEEP_ATTRS = code_insee,libdens7,nom_officiel,population,superficie_cadastrale
    -> AttributeRenamer
Note: Renomme l'attribut de classement
AttributeRenamer
    ATTR_TABLE = RENAME_SET_DEFAULT libdens7 > classement
    KEEP_RENAMED_ONLY = no
    MISSING_INPUT_ATTRS = REMOVE
    -> commune (writer GEOJSON_1)
commune (writer GEOJSON_1)
    attributes: classement string, nom_officiel string, code_insee string, population int, superficie_cadastrale int

Bookmark: DOM
Note: Guyanne
COMMUNE (reader SHAPEFILE_5)
    attributes: ID varchar(24), NOM varchar(50), NOM_M varchar(50), INSEE_COM varchar(5), STATUT varchar(26), POPULATION long, INSEE_CAN varchar(5), INSEE_ARR varchar(2), INSEE_DEP varchar(3), INSEE_REG varchar(2), SIREN_EPCI varchar(20)
    -> BulkAttributeRenamer_2
Note: GUADELOUPE D971 / BD ADMIN EXPRESS
COMMUNE (reader SHAPEFILE_1)
    attributes: ID varchar(24), NOM varchar(50), NOM_M varchar(50), INSEE_COM varchar(5), STATUT varchar(26), POPULATION long, INSEE_CAN varchar(5), INSEE_ARR varchar(2), INSEE_DEP varchar(3), INSEE_REG varchar(2), SIREN_EPCI varchar(20)
    -> BulkAttributeRenamer_2
Note: MARTINIQUE D972 / BD ADMIN EXPRESS
COMMUNE (reader SHAPEFILE_2)
    attributes: ID varchar(24), NOM varchar(50), NOM_M varchar(50), INSEE_COM varchar(5), STATUT varchar(26), POPULATION long, INSEE_CAN varchar(5), INSEE_ARR varchar(2), INSEE_DEP varchar(3), INSEE_REG varchar(2), SIREN_EPCI varchar(20)
    -> BulkAttributeRenamer_2
Note: MAYOTTE D976
COMMUNE (reader SHAPEFILE_3)
    attributes: ID varchar(24), NOM varchar(50), NOM_M varchar(50), INSEE_COM varchar(5), STATUT varchar(26), POPULATION long, INSEE_CAN varchar(5), INSEE_ARR varchar(2), INSEE_DEP varchar(3), INSEE_REG varchar(2), SIREN_EPCI varchar(20)
    -> BulkAttributeRenamer_2
Note: La REUNION
COMMUNE (reader SHAPEFILE_4)
    attributes: ID varchar(24), NOM varchar(50), NOM_M varchar(50), INSEE_COM varchar(5), STATUT varchar(26), POPULATION long, INSEE_CAN varchar(5), INSEE_ARR varchar(2), INSEE_DEP varchar(3), INSEE_REG varchar(2), SIREN_EPCI varchar(20)
    -> BulkAttributeRenamer_2

Bookmark: Transforme attribut shape et ajoute surface
BulkAttributeRenamer_2
    ATTRCHOICE_ACTION = NONPROTECTEDFME
    CASE_CHANGE_TYPE = lower
    MODE_CHOICE = RENAME
    PATTERN_ACTION_DISP = CASECHANGE
    ATTRCHOICE = All Attributes
    -> AttributeRenamer_2
AttributeRenamer_2
    ATTR_TABLE:
      RENAME_SET_DEFAULT nom > nom_officiel
      RENAME_SET_DEFAULT nom_m > nom_officiel_en_majuscules
      RENAME_SET_DEFAULT insee_com > code_insee
      RENAME_SET_DEFAULT insee_can > code_insee_du_canton
      RENAME_SET_DEFAULT insee_arr > code_insee_de_l_arrondissement
      RENAME_SET_DEFAULT insee_dep > code_insee_du_departement
      RENAME_SET_DEFAULT insee_reg > code_insee_de_la_region
      RENAME_SET_DEFAULT siren_epci > codes_siren_des_epci
    KEEP_RENAMED_ONLY = no
    MISSING_INPUT_ATTRS = REMOVE
    -> AttributeCreator
AttributeCreator
    ATTR_TABLE = SET_TO superficie_cadastrale (uint8) = @Area()
    -> FeatureMerger [REQUESTOR]
